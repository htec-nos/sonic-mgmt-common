module openconfig-routing-policy-ext {
  yang-version "1";

  namespace "http://openconfig.net/yang/routing-policy-ext";
  prefix "oc-rpol-ext";
    
  import openconfig-routing-policy { prefix oc-rpol; }
  import openconfig-policy-types { prefix oc-pol-types; }
  import openconfig-extensions { prefix oc-ext; }

  // meta
  organization
    "HTEC Group";

  contact
    "alberto.martin@htecgroup.com";

  description
    "Extension module to add action field to prefix definitions";

  oc-ext:openconfig-version "1.0.0";

  revision "2025-11-09" {
    description
      "Initial public revision of the routing policy extension model.
       Adds action field configuration to prefix definition.";
    reference
      "1.0.0";
  }

  grouping prefix-action-config {
    description
      "Configuration data for prefix-level actions";

    leaf action {
      type oc-rpol:policy-result-type;
      description
        "Action to apply when this prefix is matched.
         Valid values are ACCEPT_ROUTE, REJECT_ROUTE, or NEXT_STATEMENT";
    }
  }

  augment "/oc-rpol:routing-policy/oc-rpol:defined-sets/" +
          "oc-rpol:prefix-sets/oc-rpol:prefix-set/" +
          "oc-rpol:prefixes/oc-rpol:prefix/oc-rpol:config" {
    description
      "Add action field to prefix configuration";
    uses prefix-action-config;
  }
}
