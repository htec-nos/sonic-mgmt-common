module sonic-bgp {  
    namespace "http://github.com/Azure/sonic-bgp";  
    prefix sbgp;  
    yang-version 1.1;  

    import ietf-inet-types {
        prefix inet;
    }  

    organization
        "SONiC";

    contact
        "SONiC";

    description
        "SONIC BGP";

    revision 2025-10-27 {
        description
            "Initial revision.";
    }

    container sonic-bgp {

        container BGP_GLOBALS {

            list BGP_GLOBALS_LIST {
                key "vrf_name";

                leaf vrf_name {
                    type string;
                    description
                        "VRF name, use 'default' for default VRF";
                }

                leaf local_asn {
                    type uint32 {
                        range "1..4294967295";
                    }
                    description "local AS number";
                }

                leaf router_id {
                    type inet:ipv4-address;
                    description "Router identifier";
                }
            }
        }

        container BGP_GLOBALS_AF_NETWORK {
            list BGP_GLOBALS_AF_NETWORK_LIST {
                key "vrf_name afi_safi ip_prefix";

                leaf vrf_name {
                    type leafref {
                        path "../../../BGP_GLOBALS/BGP_GLOBALS_LIST/vrf_name";
                    }
                    description "VRF name";
                }

                leaf afi_safi {
                    type string;
                    description "Address family name and subsequent address family name";
                }

                leaf ip_prefix {
                    type inet:ip-prefix;
                    description "Network address";
                }

                leaf policy {
                    type string;
                    description "Route-map to modify the attributes";
                }

                leaf backdoor {
                    type boolean;
                    //ext:custom-validation ValidateAfisafiForBackdoor;
                    description "Indicates the backdoor route";
                }
            }
        }
    }
}
