module openconfig-bgp-annot {

    yang-version "1";

    namespace "http://openconfig.net/yang/annotation/openconfig-bgp-annot";
    prefix "oc-bgp-annot";

    import sonic-extensions { prefix sonic-ext; }
    import openconfig-bgp { prefix oc-bgp; }

    deviation /oc-bgp:bgp/oc-bgp:global {
        deviate add {
            sonic-ext:table-name "BGP_GLOBALS";
            sonic-ext:key-transformer "bgp_global_key_xfmr";
        }
    }

    deviation /oc-bgp:bgp/oc-bgp:global/oc-bgp:config/oc-bgp:as {
        deviate add {
            sonic-ext:field-name "local_asn";
        }
    }

    deviation /oc-bgp:bgp/oc-bgp:global/oc-bgp:config/oc-bgp:router-id {
        deviate add {
            sonic-ext:field-name "router_id";
        }
    }

    deviation /oc-bgp:bgp/oc-bgp:global/oc-bgp:state/oc-bgp:as {
        deviate add {
            sonic-ext:field-name "local_asn";
        }
    }

    deviation /oc-bgp:bgp/oc-bgp:global/oc-bgp:state/oc-bgp:router-id {
        deviate add {
            sonic-ext:field-name "router_id";
        }
    }
}
